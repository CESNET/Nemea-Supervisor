module "nemea" {
  namespace "urn:ietf:params:xml:ns:yang:nemea";
  prefix "nemea";
	include "trap-interfaces";
  organization "CESNET, z.s.p.o.";
  contact "cejkat@cesnet.cz";
  description "Module specifying configuration of Nemea supervisor.";
  revision "2017-08-02" { description "First version"; }


  container "nemea-supervisor" {
    list "module-group" {
			description "TODO";
      key "name";
      leaf "name" {
        type "string" {
          length "1..255";
          pattern "[0-9a-zA-Z _-]+";
        }
				mandatory "true";
        description "Name of group of Nemea modules.";
      }
      leaf "enabled" {
        type "boolean";
        description "Activation of group of Nemea modules.";
      }
    
      list "module" {
				description "TODO";
        key "name";
        leaf "name" {
          type "string" {
            length "1..255";
            pattern "[0-9a-zA-Z _-]+";
          }
					mandatory "true";
          description "Unique name of the module instance.";
        }
        leaf "path" {
          type "string" {
						pattern "^/.+";
          }
          mandatory "true";
          description "Full path to where module binary resides.";
        }

				list "instance" {
					description "One module can be configured in various ways. To store all
												and refer them, this instance list is used.";
					key "name";
					leaf "name" {
        	  type "string" {
        	    length "1..255";
        	    pattern "[0-9a-zA-Z _-]+";
        	  }
						mandatory "true";
        	  description "Unique name of the module instance.";
        	}

					leaf "enabled" {
        	  type "boolean";
        	  mandatory "true";
        	  description "Specifies whether to start the module or not.";
        	}
        	leaf "params" {
        	    type "string";
        	}
        	leaf "max-restarts-per-min" {
        	  type "uint8";
        	  default "3";
        	  description "How many times the module will be automatically restarted (in case it
						             terminated) before setting disabled";
        	}
					leaf "last-pid" {
						type "uint32" {	range "1..max"; }
						description "In case supervisor was interrupted and shouldn't have stopped the
												 modules, PID of this Nemea module process is stored so that
												 supervisor can reconnect to it once it starts again.";
					}
					leaf "sr-enabled" {
						type "boolean";
						default "false";
						description "Specifies whether module has it's own YANG model derived from Nemea module template and is capable of loading configuration from Sysrepo when passed -sr 'INSTANCE_NAME'. INSTANCE_NAME is ";
					}

					container "specific-conf" {
						leaf name {
							type string;
						}
						//when "../sr-enabled = 'true'";
						// Insert augments here
					} // End container "specific-conf"

					container "stats" {
						config "false";
						description "TODO";

	      	  leaf "running" {
	      	    type "boolean";
	      	    description "Specify whether the module is running.";
	      	  }
	      	  leaf "restart-counter" {
	      	    type "uint8";
	      	    description "The number of repeated starts of the module.";
	      	  }
						leaf "cpu-user" {
							type "uint64";
							description "TODO";
						}
						leaf "cpu-kern" {
							type "uint64";
							description "TODO";
						}
						leaf "mem-vms" {
							type "uint64";
							description "TODO";
						}
						leaf "mem-rss" {
							type "uint64";
							description "TODO";
						}
					} // End container "stats"

				} // End list "instance"

				uses "trap-ifcs-list";

      } // End list "module"
    } // End list "module-group"
  } /* End container nemea-supervisor */
}
