module "nemea-module-asdf" {
  namespace "urn:ietf:params:xml:ns:yang:asdf";
  prefix "asdf";

	import "nemea" {
		prefix "nemea";
	}

  organization "CESNET, z.s.p.o.";
  contact "cejkat@cesnet.cz";
  description "Module specifying configuration of Nemea supervisor.";
  revision "2017-08-03" { description "First version"; }


	//augment "/nemea:nemea-supervisor/nemea:module-group/nemea:module/nemea:instance/nemea:specific-conf" {
	augment "/nemea:nemea-supervisor/nemea:module-group/nemea:module/nemea:instance/nemea:specific-conf" {
		when "../../nemea:name = 'asdf'";
		leaf "another-leaf" {
			type "string";
		}
	}
/*
takhle to funguje, import i export
blby je ze `to neupozorni, kdyz tam ta when podminka neni splnena

	augment "/nemea:nemea-supervisor/nemea:module-group/nemea:module/nemea:instance" {
		when "nemea:name = 'xx'";
		leaf "blabla" {
			type "string";
		}
	}
	*/

/*
	augment "/nemea:nemea-supervisor/nemea:module-group" {
		when "nemea:name = 'test-module'";
		leaf "blabla" {
			type "string";
		}
	} */

}
