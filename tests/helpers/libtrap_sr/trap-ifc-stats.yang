module "libtrap" {
  namespace "urn:ietf:params:xml:ns:yang:nemea";
  prefix "libtrap";
  organization "CESNET, z.s.p.o.";
  contact "cejkat@cesnet.cz";
  description "TODO";
  revision "2017-10-19" { description "First version"; }


  container "trap-ifc-stats" {
		config false;
		leaf "pid" {
			type "uint16";
			mandatory true;
		}
			
		list "module" {
			key "pid";
		}

			leaf "ifc_state" {

			}
			leaf "ifc_id" {

			}
			leaf "ifc_type" {

			}
			leaf "messages" {

			}
			leaf "buffers" {

			}


		}
	}



    /* Begin list module-group */
    list "module-group" {
      key "name";
      leaf "name" {
        type "string";
        description "Name of group of Nemea modules_ll.";
      }
      leaf "enabled" {
        type "boolean";
        description "Activation of group of Nemea modules_ll.";
      }
      /* Begin list module */
      list "module" {
        key "name";
        leaf "name" {
          type "string";
          description "Unique name of the module.";
        }
				// TODO sjednotit zpatky do exec-path nebo tak neceho
        leaf "exec-name" {
          type "string";
          mandatory "true";
          description "Name of module binary.";
        }
        leaf "path" {
          type "string" {
						pattern "^/.+/$";
          }
          mandatory "true";
          description "Full path to where module binary resides.";
        }
        leaf "enabled" {
          type "boolean";
          mandatory "true";
          description "Specify whether to start the module or not.";
        }
        leaf "params" {
            type "string";
        }
        leaf "module-restarts" {
          type "uint8";
          default "3";
          description "How many times the module will be automatically restarted (in case it
          terminated) before setting disabled";
        }

				uses "trap-ifcs-list";

        leaf "running" {
          type "boolean";
          config "false";
          description "Specify whether the module is running.";
        }
        leaf "restart-counter" {
          type "uint8";
          config "false";
          description "The number of repeated starts of the module.";
        }
       }
       /* End List module */
      }
    /* Begin list module-group */
    }
}
